module subscriber-server {
  yang-version 1.1;
  namespace "http://tail-f.com/ns/cleu24/tecops-2665/subscriber-server";
  prefix "tc-subscriber";

  import ietf-inet-types {
    prefix inet;
  }


  /* DATA NODES */
  container subscriber-server {
    list subscribers {
      key subscriber-id;
      leaf subscriber-id { type string; }

      leaf video-edge-streamer {
        type inet:host;
      }

      leaf video-cpe {
        type inet:host;
      }
    }
  }
}
