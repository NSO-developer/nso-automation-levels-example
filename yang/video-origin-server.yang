module video-origin-server {
  yang-version 1.1;
  namespace "http://tail-f.com/ns/cleu24/tecops-2665/video-origin-server";
  prefix "tc-origin";


  /* GROUPINGS */
  grouping ingest {
    leaf buffer-fill {
      config false;
      type uint8 {
        range 0..100;
      }
      units "percent";
      description
        "Buffer fill in percent.";
    }
  }

  grouping egress {
    leaf egress-speed {
      config false;
      type uint64 {
        range 0..max;
      }
      units "KiB/s";
      description
        "Egress speed in KiB/s.";
    }
    leaf egress-traffic {
      config false;
      type uint64 {
        range 0..max;
      }
      units "KiB";
      description
        "Egress traffic in KiB.";
    }
  }

  /* DATA NODES */
  container video-origin-server {
    description
      "The video origin server.";

    // Totals for the server
    uses egress;

    list content {
      description
        "List of content available on the video origin server.";

      key content-id;
      leaf content-id {
        type string;
      }

      // Metrics per content
      uses ingest;
      uses egress;
    }
  }
}
