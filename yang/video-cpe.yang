module video-cpe {
  yang-version 1.1;
  namespace "http://tail-f.com/ns/cleu24/tecops-2665/video-cpe";
  prefix "tc-cpe";

  import ietf-inet-types {
    prefix inet;
  }


  /* DATA NODES */
  container video-cpe {
    leaf video-edge-streamer {
      type inet:host;
    }

    leaf subscriber-server {
      type inet:host;
    }
  }
}
