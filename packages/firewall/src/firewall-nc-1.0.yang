module firewall-nc-1.0 {
  yang-version 1.1;
  namespace "http://tail-f.com/ns/ned-id/firewall-nc-1.0";
  prefix firewall-nc-1.0;

  import firewall-nc {
    prefix family;
  }

  identity firewall-nc-1.0 {
    base family:firewall-nc;
  }
}
