module origin {
  yang-version 1.1;
  namespace "http://tail-f.com/ns/cleu24/tecops-2665/origin";
  prefix tc-origin;

  import ietf-inet-types {
    prefix inet;
  }
  import tailf-common {
    prefix tailf;
  }


  /* GROUPINGS */
  grouping ingest {
    leaf buffer-fill {
      config false;
      type uint8 {
        range 0..100;
      }
      units "percent";
      description
        "Buffer fill in percent.";
    }
  }

  grouping egress {
    leaf egress-speed {
      config false;
      type uint64 {
        range 0..max;
      }
      units "KiB/s";
      description
        "Egress speed in KiB/s.";
    }
    leaf egress-traffic {
      config false;
      type uint64 {
        range 0..max;
      }
      units "KiB";
      description
        "Egress traffic in KiB.";
    }
  }

  /* DATA NODES */
  container origin {
    description
      "The media origin server.";

    leaf streaming-port {
      description
        "The port where origin and edge streamers handle content data.";
      type inet:port-number;
    }

    list edge {
      description
        "List of configured edge streamers.";
      key hostname;
      leaf hostname {
        type inet:host;
      }
      leaf streaming-port {
        description
          "The port where origin and edge streamers handle content data.";
        type inet:port-number;
      }
    }

    // Totals for the server
    uses ingest;
    uses egress;

    list content {
      description
        "List of content available on the media origin server.";

      key content-id;
      leaf content-id {
        type string;
      }

      // Metrics per content
      uses ingest;
      uses egress;

    }
  }

  /* RPCs */
  rpc load-from-storage {
    tailf:actionpoint load-from-storage;
    description
      "Load the content from storage.";
  }
}
