module origin-ann {
  yang-version 1.1;
  namespace "http://tail-f.com/ns/cleu24/tecops-2665/origin-ann";
  prefix tc-origin-ann;

  import origin {
    prefix tc-origin;
  }
  import tailf-common {
    prefix tailf;
  }

  /* totals metrics */

  /* ingest */

  tailf:annotate "/tc-origin:origin/tc-origin:buffer-fill" {
    tailf:callpoint "origin";
  }

  /* egress */

  tailf:annotate "/tc-origin:origin/tc-origin:egress-speed" {
    tailf:callpoint "origin";
  }
  tailf:annotate "/tc-origin:origin/tc-origin:egress-traffic" {
    tailf:callpoint "origin";
  }


  /* per content metrics */

  /* ingest */

  tailf:annotate "/tc-origin:origin/tc-origin:content" +
                 "/tc-origin:egress-speed" {
    tailf:callpoint "origin";
  }

  /* egress */

  tailf:annotate "/tc-origin:origin/tc-origin:content" +
                 "/tc-origin:egress-traffic" {
    tailf:callpoint "origin";
  }
  tailf:annotate "/tc-origin:origin/tc-origin:content" +
                 "/tc-origin:buffer-fill" {
    tailf:callpoint "origin";
  }
}
