module edge-nc-1.0 {
  yang-version 1.1;
  namespace "http://tail-f.com/ns/ned-id/edge-nc-1.0";
  prefix edge-nc-1.0;

  import edge-nc {
    prefix family;
  }

  identity edge-nc-1.0 {
    base family:edge-nc;
  }
}
