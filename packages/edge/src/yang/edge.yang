module edge {
  yang-version 1.1;
  namespace "http://tail-f.com/ns/cleu24/tecops-2665/edge";
  prefix "tc-edge";

  import ietf-inet-types {
    prefix inet;
  }
  import tailf-common {
    prefix tailf;
  }


  /* GROUPINGS */
  grouping ingest {
    leaf buffer-fill {
      config false;
      type uint8 {
        range 0..100;
      }
      units "percent";
      description
        "Buffer fill in percent.";
    }
  }

  grouping ingress {
    leaf ingress-speed {
      config false;
      type uint64 {
        range 0..max;
      }
      units "KiB/s";
      description
        "Ingress speed in KiB/s.";
    }
    leaf ingress-traffic {
      config false;
      type uint64 {
        range 0..max;
      }
      units "KiB";
      description
        "Ingress traffic in KiB.";
    }
    leaf jitter {
      config false;
      type decimal64 {
        fraction-digits 3;
      }
      units "seconds";
      description
        "Packet Delay Variation, i.e. packet-jitter, in seconds.";
      reference
        "RFC 3393: IP Packet Delay Variation Metric for IP Performance
                   Metrics (IPPM)";
    }
  }

  grouping egress {
    leaf egress-speed {
      config false;
      type uint64 {
        range 0..max;
      }
      units "KiB/s";
      description
        "Egress speed in KiB/s.";
    }
    leaf egress-traffic {
      config false;
      type uint64 {
        range 0..max;
      }
      units "KiB";
      description
        "Egress traffic in KiB.";
    }
  }


  /* DATA NODES */
  container edge {
    description
      "The edge streaming server.";

    leaf streaming-port {
      description
        "The port where origin and edge streamers handle content data.";
      type inet:port-number;
    }

    leaf origin-server {
      description
        "The configured media origin server.";
      type inet:host;
    }

    leaf subscriber-server {
      description
        "The configured subscriber server.";
      type inet:host;
    }

    // Totals for the server
    uses ingest;
    uses ingress;
    uses egress;

    list content {
      description
        "List of content available on the edge streamer server.";

      key content-id;
      leaf content-id {
        type string;
      }

      // Metrics per content
      uses ingest;
      uses ingress;
      uses egress;
    }
  }

  /* RPCs */
  rpc toggle-jitter {
    tailf:actionpoint toggle-jitter;
    description
      "Toggle high/low jitter, this will trigger a data center switch.";
  }
}
