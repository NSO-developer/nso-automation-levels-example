module cpe-nc {
  yang-version 1.1;
  namespace "http://tail-f.com/ns/ned-id/cpe-nc";
  prefix cpe-nc;

  import tailf-common {
    prefix tailf;
  }

  import tailf-ncs-ned {
    prefix ned;
  }

  identity cpe-nc {
    tailf:abstract;
    base ned:netconf-ned-id;
  }
}
