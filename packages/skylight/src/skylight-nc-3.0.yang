module skylight-nc-3.0 {
  yang-version 1.1;
  namespace "http://tail-f.com/ns/ned-id/skylight-nc-3.0";
  prefix skylight-nc-3.0;

  import skylight-nc {
    prefix family;
  }

  identity skylight-nc-3.0 {
    base family:skylight-nc;
  }
}
