module accedian-metadata {
    yang-version 1.1;
    namespace urn:accedian:params:xml:ns:yang:accedian-metadata;
    prefix accedian-metadata;

    import accedian-gateway-orchestrator {
        prefix gateway-orchestrator;
        revision-date 2022-02-15;
    }

    organization
      "Accedian";

    contact
      "Web URL: https://accedian.com/
       E-mail: info@accedian.com
          Phone:   1.514.331.6181 or +1.866.685.8181";

    description
      "This yang module defines Accedian Metadata configuration for Analytics";

    revision 2022-02-15 {
        description
          "Initial Revision";
        reference
          "accedian-metadata : Metadata configuration";
    }
    typedef severity {
        type enumeration{
            enum "informational" {
                description
                  "severity is informational";
            }
            enum "low" {
                description
                  "severity is low";
            }
            enum "medium" {
                description
                  "severity is medium";
            }
            enum "high" {
                description
                  "severity is high";
            }
            enum "critical" {
                description
                  "severity is critical";
            }
        }
        description
          "defined severity in system";
    }
    typedef comparator {
        type enumeration{
            enum "gt" {
                description
                  "grater than";
            }
            enum "lt" {
                description
                  "lesser than";
            }
            enum "eq" {
                description
                  "equal";
            }
            enum "gte" {
                description
                  "grater than equal";
            }
            enum "lte" {
                description
                  "lesser than equal";
            }
            enum "in" {
                description
                  "in condition";
            }
        }

        description
          "defined comparator";
    }
    typedef metric-type {
        type enumeration{
            enum "session" {
                description
                  "Metric type session";
            }

            enum "capture" {
                description
                  "Metric type capture";
            }

            enum "security" {
                description
                  "Metric type security";
            }
        }
        description
          "Metric Type definition";
    }

    typedef killchain {

        type enumeration {
            enum "ActionsOnObjective" {

                description
                  "Killchain : Actions on Objective";
            }
            enum "CommandAndControl" {

                description
                  "Killchain : Command And Control";
            }
            enum "Exfiltration" {

                description
                  "Killchain : Ex filtration";
            }
            enum "Exploitation" {

                description
                  "Killchain : Exploitation";
            }
            enum "Reconnaissance" {

                description
                  "Killchain : Reconnaissance";
            }
        }
        description
          "Killchain of an alert";
    }

    grouping location {

        leaf name {
            type string;
            description
              "location name";
        }

        leaf latitude {
            // type uint32; // -90 to +90 range : how to define
            type decimal64 {

                fraction-digits 8;
            }
            description
              "Latitude of the site";
        }

        leaf longitude {
            // type uint32; // -90 to +90 range : how to define
            type decimal64 {

                fraction-digits 8;
            }
            description
              "longitude of the site";
        }
        description
          "Group of attributes to represent a location";
    }

    grouping tenant {
        leaf tenantId {

            type string;
            config false;
            description
              "Tenant Id from which the alert is raised";
        }

        leaf tenantName {
            type string;
            config false;
            description
              "Tenant name from which the alert is raised";
        }
        description
          "group of attributes to define a Tenant";
    }

    container metadata {
        description
          "Top level container to represent metadata associated with monitored objects";
        list monitoredObject {
            key objectId;
            leaf objectId {
//                type leafref{
//                    path "/gateway-orchestrator:sessions/gateway-orchestrator:session/gateway-orchestrator:sessionIdentifier";
//                }
            	type string;
                description
                  "Object ID to tag with the monitored object session";
            }
            leaf objectName {
                when "/gateway-orchestrator:sessions/gateway-orchestrator:session[gateway-orchestrator:sessionIdentifier=current()/../objectId]/gateway-orchestrator:orchestratorType='agent'";
//                type leafref{
//                    path "/gateway-orchestrator:sessions/gateway-orchestrator:session[gateway-orchestrator:sessionIdentifier=current()/../objectId]/gateway-orchestrator:agent/gateway-orchestrator:agentSessionName";
//                }
                type string;
                description
                  "Object Name to tag with the monitored object session";
            }
            leaf actuatorName {
            	type string;
            }
            leaf actuatorType {
            	type string;
            }
            leaf reflectorName {
            	type string;
            }
            leaf reflectorType {
            	type string;
            }
            leaf objectType {
            	type string;
            }
            container geo {
                description
                  "Geo metadata";

                container startPoint {
                    uses location;
                    description
                      "denotes starting point of metadata config";
                }

                container endPoint {
                    uses location;
                    description
                      "denotes ending point of metadata config";
                }
            }
            leaf-list topology {
                type string;
                description
                  "list of topology points";
            }
            list metadataElement {
                key name;
                description
                  "List of meta data";
                leaf name {
                    type leafref{
                        path "/metadataCategories/metadataCategory/name";
                    }
                    description
                      "KeyName of the meta data list";
                }
                leaf value {
                    type "string";
                    description
                      "value of the meta data list entry";
                }
            }
            description
              "list of monitored object";
        }
    }
    container metadataCategories {
        description
          "Represents all Metadata category configuration";

        uses tenant;

        list metadataCategory {
            description
              "represents metadata category";
            key name;
            leaf name {
                type string;
                description
                  "name of the metadata category";
            }
            leaf isActive {
                type boolean;
                description
                  "if the metadata category is active or not";
            }
        }
    }
}
