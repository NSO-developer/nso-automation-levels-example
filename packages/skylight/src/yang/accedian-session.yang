submodule accedian-session {

    yang-version 1.1;

    belongs-to "accedian-gateway-orchestrator" {
        prefix "gateway-orchestrator";
    }

    import accedian-common {
        prefix common;
    }

    import ietf-inet-types {
        prefix inet;
    }
    import accedian-twamp {
        prefix accedian-twamp;
    }

    import accedian-throughput {
        prefix accedian-throughput;
    }

    organization
      "Accedian";

    contact
      "Web URL: https://accedian.com/
       E-mail: info@accedian.com
          Phone:   1.514.331.6181 or +1.866.685.8181";

    description
      "This yang module defines skylight  session configuration";

    revision 2022-02-15 {
        description
          "Initial Revision";
        reference
          "accedian-session : Session configuration";
    }

    typedef supportedActionBycontrolSession {
        type enumeration{
            enum "start" {
                description
                  "Start session";
            }
            enum "stop" {
                description
                  "stop session";
            }
        }
    }
    typedef reflector-mode {

        type enumeration {
            enum "stateful" {
                description
                  "twamp-stateful Session";
            }
            enum "stateless" {
                description
                  "twamp-stateless Session";
            }
        }
        description
          "Indicates reflector mode configuration";
    }

    grouping session-statistics {
        description
          " Group conatins the session statistics information";
        leaf statusMessage {
            type string;
            config false;
            description
              "Descriptive message of the session-status";
        }
        leaf state {
            type common:session-State;
            config false;
            description
              "Indicates state of session";
        }
        leaf captureTime {
            type string;
            config false;
            description
              "Capture time for session execution";
        }
    }

    grouping interface-attributes-group {
        leaf endpointName {

            /*type leafref{
                path "/gateway-orchestrator:accedian-components/sensor-control/endpoints/endpoint/name";
            }*/
            type string;
            description
              "endpoint name connected with the session";
        }
        leaf interfaceName {
            config false;
            /*type leafref{
                path "/gateway-orchestrator:accedian-components/sensor-control/endpoints/endpoint[name=current()/../endpointName]/interfaces/interface/name";
            }*/
            type string;
            description
              "endpoint interface connected with the session";
        }

        leaf port {
            type inet:port-number;
            description
              "interface port";
        }

        leaf ip-address {
            config false;
            /*type leafref{
                path "/gateway-orchestrator:accedian-components/sensor-control/endpoints/endpoint[name=current()/../endpointName]/interfaces/interface[name=current()/../interfaceName]/ipaddress/ip";
            }*/
            type string;
            description
              "ip address";
        }
    }

    grouping session-list-group {
        description
          "grouping list of sessions ";

        list session {

            key "sessionIdentifier orchestratorType";
            description
              "a session to establish connectivity";
            leaf sessionIdentifier {
                type string;
                description
                  "Unique Id to identify a session ";
            }
            leaf orchestratorType {
                type common:orchestratorType;
                description
                  "Orchestrator Type to identify if the session is for Agengt or control orchestrator";
            }

            leaf sessiontype {
                type common:session-type;
                description
                  "Indicates Session Type";
            }
            leaf ifStateful {
                type boolean;
                description
                  "Indicates if the session mode is stateful or stateless";
            }

            container agent {
                when "../orchestratorType = 'agent'";

                leaf agentId {
                    type leafref {
                        path "/gateway-orchestrator:accedian-components/sensor-agent/agents/agent/agentId";
                    }
                    description
                      "agent Id";
                }
                leaf agentSessionName {
                    type string;
                    description
                      "Session Name configured on agent";
                }
                leaf enable {
                    type boolean;
                    default true;
                    description
                      "whether the session is Enable or not";
                }
                leaf period {
                    type string;
                    default "continuous";
                    description
                      "Period of the session";
                }
                description
                  "Agent linked with the session";
            }

            container control {
                when "../orchestratorType = 'control'";
                leaf description {
                    type string;
                    description
                      " description of the control session";
                }
                leaf addressFamily {
                    type common:addressFamily;
                    default ipv4;
                    description
                      "Address family used in the session";
                }
                leaf gateWayAddress {
                    type inet:ip-address;
                    description
                      "Indicates the gateway address of the session";
                }
                leaf dscp {
                    type inet:dscp;
                    default "0";
                    description
                      "dscp for the control session";
                }

                container source {
                    uses interface-attributes-group;
                    description
                      "specifies source endpoint properties";
                }

                container destination {
                    uses interface-attributes-group;
                    description
                      "specifies destination endpoint properties";
                }

                container connectionParameters {
                    description
                      "specifies connection related parameters";
                    leaf interval {
                        type uint32{
                            range 5..900;
                        }
                        default 30;
                        description
                          "interval period";
                    }

                    leaf tos {
                        type uint8{
                            range 0..255;
                        }
                        default 0;
                        description
                          "type of Service";
                    }
                    leaf ttl {
                        type uint8{
                            range 1..255;
                        }
                        default 255;
                        description
                          "time to live";
                    }

                    leaf vprio {
                        type uint8{
                            range 0..7;
                        }
                        default 0;
                        description
                          "time to live";
                    }
                }

                leaf-list labels {
                    type string;
                    description
                      "List of session labels";
                }
                container stream {

                    description
                      "Represents the Session Stream configuration";

                    leaf payloadSize {
                        type uint32;

//                        mandatory true;
                        description
                          "Payload size of the session Stream";
                    }
                    leaf pps {

                        type decimal64 {
                            range 0.1..200;
                            fraction-digits 2;
                        }
                        mandatory true;
                        description
                          "indicates Packet per second";
                    }
                    leaf type {
                        type common:session-stream-type;
                        description
                          "Indicates the media type of the session stream";
                    }
                }

                action operateControlSession {
                    description
                      "operations to be performed on control session";

                    input {
                        leaf actionName {
                            type supportedActionBycontrolSession;
                            description
                              "Name of the action to be triggered";
                        }
                    }
                }

                description
                  "Sensor control linked with the session";
            }

            container twamp {
                when "../sessiontype= 'twamp' and  ../orchestratorType = 'agent'";
                uses accedian-twamp:twamp-sender;
                uses accedian-twamp:twamp-reflector;
                uses accedian-twamp:twamp-ctrl-client-connection;
                description
                  "Top level container for TWAMP protocol";
            }
            container throughput {
                when "../sessiontype= 'throughput' and ../orchestratorType = 'agent'";

                uses accedian-throughput:throughput-group;
                description
                  "Top level container for Throughput protocol || For Sensor Control Throughput is not supported";
            }

            uses session-statistics;
        }
    }
}
