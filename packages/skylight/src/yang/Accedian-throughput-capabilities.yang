module Accedian-throughput-capabilities {
  yang-version 1.1;
  namespace "http://accedian.com/ns/yang/session/cap/throughput";
  prefix acdtpc;

  import Accedian-session-type {
    prefix acdst;
  }

  import Accedian-service-endpoint {
    prefix acdsep;
  }

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "This module contains the type definitions of Throughput capabilities.

    Copyright (c) Accedian Networks, Inc.
    All rights reserved";

  revision 2024-08-31 {
    description
      "Initial revision";
  }

  augment "/acdsep:service-endpoints/acdsep:service-endpoint/acdsep:state/acdsep:capabilities/acdsep:session-capabilities" {
    when "derived-from-or-self(/acdsep:service-endpoints/acdsep:service-endpoint/acdsep:state/acdsep:capabilities/acdsep:session-type, 'acdst:throughput')";
    description
      "Augment Accedian service-endpoint capabilities with throughput specific capabilities";

    container throughput-capabilities {
      description
        "Throughput specific capabilities";


      list capability {
        key capability-key;
        description
          "List of key-value where each entry represents a Throughput capability and it's corresponding
          value. The type of each value is key specific and is described in the key description";

        leaf capability-key {
          description
            "A leaf representing a Throughput capability. The meaning of each capability and its value
            is described in the following enumeration";
          type enumeration {
            enum "sender" {
              description
                "Boolean key to indicate if the endpoint can act as a throughput sender";
            }
            enum "reflector" {
              description
                "Boolean key to indicate if the endpoint can act as a throughput reflector";
            }
            enum "number-of-reflectors" {
              description
                "Integer representing the number of reflector supported by the endpoint. Each extra
                reflector is specified using a different Throughput reflector port";
            }
          }
        }

        leaf capability-value {
          type acdst:capability-value;
          description
            "The value associated with each Throughput capability key. The value depends on the
            key. The value type is provided in the key description";
        }
      }
    }
  }
}
