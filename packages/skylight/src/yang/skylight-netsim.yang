module skylight-netsim {
  namespace "http://tail-f.com/pkg/skylight-netsim";
  prefix skylight-netsim;

  import tailf-common { prefix tailf; }
  import Accedian-type { prefix acdt; }
  import Accedian-service-endpoint { prefix accsep; }
  import Accedian-service-endpoint-type { prefix acdsept; }

  organization "Cisco Systems";
  contact "<support@tail-f.com>";

  description
    "Skylight netsim models.";

  revision 2023-12-14 {
    description
      "Inital version.";
  }

  typedef jitter-dev {
    type decimal64 {
      fraction-digits 3;
    }
    units ms;
  }

  grouping jitter-grouping {
    leaf device {
      description "Name of the device this notification pertains to.";
      mandatory true;
      type acdt:id;
      tailf:non-strict-leafref {
        path "/acdsep:service-endpoints" +
             "/acdsep:service-endpoint/acdsep:endpoint-id";
       }   
    }
    leaf jitter {
      description "Optional jitter value. If not specified, 
        a simulated value will be generated automatically.";
      type jitter-dev;
    }
  }

  grouping alerts-grouping {
    leaf type {
      description "Notifications to send.";
      type enumeration {
        enum jitter {
          description "Send a jitter event.";
          tailf:code-name "enum_jitter";
        }
        enum alert {
          description "Send an alert event.";
          tailf:code-name "enum_alert";
        }
        enum jitter-alert {
          description "Send both jitter and alert events.";
          tailf:code-name "enum_jitter_alert";
        }
      }
      default jitter;
    }
  }

  rpc send-notification-high {
    tailf:actionpoint "skylight-send-notification";
    input {
      uses jitter-grouping;
      uses alerts-grouping;
    }
  }
  rpc send-notification-low {
    tailf:actionpoint "skylight-send-notification";
    input {
      uses jitter-grouping;
      uses alerts-grouping;
    }
  }


  notification jitter-event {
    description
      "Jitter event emitted from the Skylight Netsim device.";
    leaf device {
      description "Name of the device this notification pertains to.";
      mandatory true;
      type string;
    }
    leaf jitter {
      description "Jitter observed pertaining to the device.";
      mandatory true;
      type jitter-dev;
    }
  }
}
