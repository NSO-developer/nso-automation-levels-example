module Accedian-session-throughput {
  yang-version 1.1;
  namespace "http://accedian.com/ns/yang/session/throughput";
  prefix acdstp;

  import ietf-inet-types {
    prefix inet;
  }

  import Accedian-net-type {
    prefix acdnt;
  }

  import Accedian-session {
    prefix acdses;
  }

  import Accedian-session-type {
    prefix acdstype;
  }

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "The throughput session type implements support for
    the RFC6349 framework for TCP througput measurements.

    Copyright (c) Accedian Networks, Inc.
    All rights reserved";

  revision 2024-08-31 {
    description
      "Initial revision";
  }

  augment "/acdses:sessions/acdses:session/acdses:service-endpoints/acdses:session-protocol" {
    when "derived-from-or-self(/acdses:sessions/acdses:session/acdses:session-type, 'acdstype:throughput-session')" {
      description
        "Augment the service session protocol of Accedian-service-session with throughput
        config data";
    }

    container throughput {
      description
        "Throughput session configuration data";

      container session-sender {
        description
          "Throughput packet sender configuration data";

        leaf admin-state {
          type boolean;
          default false;
          description
            "Indicates whether the associated session
            endpoint is operating as a throughput test
            packet sender";
        }

        leaf reflector-ip {
          type inet:ip-address;
          description
            "The IP address belonging to the remote
            Session-Reflector device to which the Throughput Test
            session will be initiated.
            If not specified, the address configured in the peered
            service-session-endpoint will be used.
            If a peered endpoint is not defined or if the reflector doesn't
            specify an address, an error will be returned";
        }

        leaf reflector-port {
          type inet:port-number;
          description
            "This parameter defines the port number used by the
            Session-Sender as the destination port for this Throughput test session. It is
            used in scenarios where the transmitted destination port must be different from
            the port value expected by the session-reflector. This is typically required
            on network paths where the destination port is translated to a different value. For
            example, with NAT and/or port forwarding.

            If a value for this field is not provided, the value configured
            in session-reflector/reflector-udp-port will be used";
        }

        leaf reverse {
          type boolean;
          default false;
          description
            "False means TCP traffic from agent-to-server";
        }

        leaf duration {
          type uint32 {
            range "0..86400";
          }
          units seconds;
          default 60;
          description
            "Duration for the throughput test. testDurationSecs is ignored by the baseline test";
        }

        leaf report-interval {
          type uint8 {
            range "1..60";
          }
          units seconds;
          default 1;
          description
            "Throughput test metrics reporting interval. testReportIntervalSecs is
            ignored by the baseline test";
        }

        leaf parallel {
          type uint8 {
            range "1..128";
          }
          default 1;
          description
            "The number of simultaneous connections to make to the server";
        }

        leaf dscp {
          type acdnt:dscp;
          description
            "The Differentiated Services Code Point values in the IP header";
        }

        leaf traceroute-dest-port {
          type inet:port-number;
          default 33434;
          description
            "Destination IP port of the traceroute probe";
        }

        leaf network-max-rate {
          type uint32;
          units bits-per-second;
          default 0;
          description
            "Maximum rate in baseline and throughput test phase. Zero means unbound";
        }

        leaf network-mtu {
          type uint16 {
            range "0..9000";
          }
          units bytes;
          default 1500;
          description
            "Maximum Transmission Unit. This parameter is required by the throughput
            test. This parameter can be omitted or set to zero before running the baseline test
            to request for discovery";
        }

        leaf network-bottleneck-bandwidth {
          type uint32;
          units bits-per-second;
          default 250000000;
          description
            "TCP bottleneck bandwidth. This parameter is required by the throughput
            test. This parameter can be omitted or set to zero before running the baseline test to
            request for discovery";
        }

        leaf network-rtt {
          type decimal64 {
            fraction-digits 3;
          }
          units milliseconds;
          default 1.0;
          description
            "Round-trip time";
        }
      }

      container session-reflector {
        description
          "Throughput packet destination configuration data";

        leaf admin-state {
          type boolean;
          default false;
          description
            "Indicates whether the associated session
            endpoint is operating as a throughput destination";
        }

        leaf reflector-port {
          type inet:port-number;
          default 5201;
          description
            "Port number of the throughput packet reflector";
        }
      }
    }
  }
}
