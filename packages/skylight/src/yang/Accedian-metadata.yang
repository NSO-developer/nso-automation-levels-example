module Accedian-metadata {
  yang-version 1.1;
  namespace "http://accedian.com/ns/yang/metadata";
  prefix acdmeta;

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "Accedian yang model Skylight Alarms.

    Copyright (c) Accedian Networks, Inc.
    All rights reserved";

  revision 2024-08-31 {
    description
      "Initial revision";
  }

  grouping metadata-list {
    list key-value {
      key key-name;
      description
        "A list of metadata key-value";

      leaf key-name {
        type leafref {
          path "/acdmeta:metadata-config/acdmeta:metadata-key/acdmeta:key-name";
        }
        description
          "The value of the key in the metadata key/value pair. The key here must be one of the existing keys
          configured in the Accedian-metadata module in metadata/metadata-key";
      }
      leaf value {
        type string;
        description
          "The value associated to the key-name";
      }
    }
  }

  container metadata-config {
    description
      "Global metadata configuration";

    list metadata-key {
      key key-name;
      max-elements 46;
      description
        "List of key that must be used when specifying a key/value in a session or
        service. The list is global for all model elements using metadata";
      leaf key-name {
        type string {
          pattern '[a-z_0-9]*';
        }
        description
          "The key definition";
      }
    }
  }
}
