module Accedian-sat {
  yang-version 1.1;
  namespace "http://accedian.com/ns/yang/session/sat";
  prefix acds;

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "This module contains the type definitions and RPCs for SAT.

    Copyright (c) Accedian Networks, Inc.
    All rights reserved";

  revision 2024-08-31 {
    description
      "Initial revision";
  }

  typedef report-data {
    type string;
    description
      "The report data as a single continuous string";
  }

  typedef report-name {
    type string;
    description
      "The name of a SAT report";
  }

  rpc get-available-reports {
    description
      "Provides a list of all test reports available for a specific session-id";
    input {
      leaf session-id {
        type string;
        mandatory true;
        description
          "Specify the for which session-id the report list should be retrieved";
      }
    }
    output {
      leaf-list available-reports {
        type string;
        description
          "Returns a list of report names";
      }
    }
  }

  rpc get-report {
    description
      "Returns the report specified by the report-name for a specific session-id";
    input {
      leaf report-name {
        type report-name;
        mandatory false;
        description
          "The name specifying the report to retrieve. If the report is not provided, the
          latest report will be retrieved";
      }

      leaf session-id {
        type string;
        mandatory true;
        description
          "The session-id associated to the requested report";
      }
    }
    output {
      leaf report-name {
        type report-name;
        description
          "The name of the retrieved report";
      }

      leaf data {
        type report-data;
        description
          "The returned report";
      }
    }
  }

  rpc delete-report {
    description
      "A remote procedure call that can be used to delete a report";
    input {
      leaf report-name {
        type report-name;
        mandatory true;
        description
          "The name of the report to delete";
      }

      leaf session-id {
        type string;
        mandatory true;
        description
          "The session-id of the report to delete";
      }
    }
  }
}
