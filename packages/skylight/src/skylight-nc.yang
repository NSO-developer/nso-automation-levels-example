module skylight-nc {
  yang-version 1.1;
  namespace "http://tail-f.com/ns/ned-id/skylight-nc";
  prefix skylight-nc;

  import tailf-common {
    prefix tailf;
  }

  import tailf-ncs-ned {
    prefix ned;
  }

  identity skylight-nc {
    tailf:abstract;
    base ned:netconf-ned-id;
  }
}
