module skylight-nc-1.0 {
  yang-version 1.1;
  namespace "http://tail-f.com/ns/ned-id/skylight-nc-1.0";
  prefix skylight-nc-1.0;

  import skylight-nc {
    prefix family;
  }

  identity skylight-nc-1.0 {
    base family:skylight-nc;
  }
}
