module Accedian-alert {
  yang-version 1.1;
  namespace "http://accedian.com/ns/yang/alert";
  prefix acdal;

  import Accedian-alert-type {
    prefix acdalt;
  }

  import ietf-yang-types {
    prefix yang;
  }

  organization
    "Accedian Networks Inc.";
  contact
    "Accedian Networks Inc.

    https://accedian.com/
    Email: info@accedian.com

    2351 Blvd Alfred-Nobel, Suite N-410
    Saint-Laurent (Montreal), Quebec,
    H4S 2A9, Canada

    Phone: +1.514.331.6181 or +1.866.685.8181";

  description
    "Accedian yang model Skylight Alarms.

    Copyright (c) Accedian Networks, Inc.
    All rights reserved";

  revision 2024-08-31 {
    description
      "Initial revision";
  }

  container alert-policies {
    description
      "Contains the configuration of the alert policies. These
      policies can be used to define under which metric types
      and conditions an alert will be generated";

    list alert-policy {
      key policy-id;
      unique policy-name;
      description
        "A list configuring alert policies. Policies can be
        referred by different model objects for monitoring and
        alerts";

      leaf policy-id {
        type string;
        description
          "The identifier of the policy";
      }

      leaf policy-name {
        type string;
        description
          "An alternate name to refer to the policy in addition to the
          policy id";
      }

      leaf description {
        type string {
          length "0..512";
        }
        description
          "A description of the policy";
      }

      leaf policy-type {
        type identityref {
          base acdalt:alert-policy;
        }
        mandatory true;
        description
          "The type of policy configured for this alert policy";
      }

      container policy {
        description
          "Policy-type specific configuration data. It is Implemented as a
          Yang augment mount point";
      }
    }
  }

  notification alert-notification {
    description
      "Alert message data structure";

    leaf policy-id {
      type string;
      description
        "The policy referred by this notification.
        The value will match one of the policy-id specified
        in /alert-policies/alert-policy/policy-id";
    }

    leaf condition-id {
      type string;
      description
        "The condition inside the policy referred by this
        notification. The value will match one of the
        condition-id specified in:
        /alert-policies/alert-policy/policy-id/conditions/condition";
    }

    leaf session-id {
      type string;
      description
        "The Session ID on which the alert is raised.
        The value matching one of the session-id specified
        in Accedian-session/sessions/session/session-id";
    }

    container service {
      description
        "Present when the alert is generated through a policy configured
        on a service";

      leaf service-id {
        type string;
        description
          "If the alert is generated through a policy configured
          on a service, this field is populated by the service-id";
      }

      leaf group-id {
        type string;
        description
          "If the alert is generated through a policy configured
          on a service, this field is populated by the group-id";
      }
    }

    leaf alert-state {
      type acdalt:alert-state;
      description
        "Current state of the alert. The different states are enumerated and
        described in Accedian-alert-type:alert-state";
    }

    leaf timestamp {
      type yang:date-and-time;
      description
        "Timestamp of the start of the alert condition";
    }

    leaf alert-severity {
      type acdalt:alert-severity;
      description
        "Severity of the alert.
        The severity reported here is based on what is configured
        in the configuration of the associated alert policy:
        /alert-policies/alert-policy/conditions/metric-severity";
    }

    leaf alert-type {
      type identityref {
        base acdalt:alert-policy;
      }
      mandatory true;
      description
        "The type of policy configured for this alert policy";
    }

    container alert-data {
      description
        "Policy specific notification data. It is Implemented as a
        Yang augment mount point";
    }
  }
}
