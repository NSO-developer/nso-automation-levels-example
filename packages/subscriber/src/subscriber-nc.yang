module subscriber-nc {
  yang-version 1.1;
  namespace "http://tail-f.com/ns/ned-id/subscriber-nc";
  prefix subscriber-nc;

  import tailf-common {
    prefix tailf;
  }

  import tailf-ncs-ned {
    prefix ned;
  }

  identity subscriber-nc {
    tailf:abstract;
    base ned:netconf-ned-id;
  }
}
