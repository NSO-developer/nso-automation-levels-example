module subscriber-nc-1.0 {
  yang-version 1.1;
  namespace "http://tail-f.com/ns/ned-id/subscriber-nc-1.0";
  prefix subscriber-nc-1.0;

  import subscriber-nc {
    prefix family;
  }

  identity subscriber-nc-1.0 {
    base family:subscriber-nc;
  }
}
